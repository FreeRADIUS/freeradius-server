FREERADIUS-NOTIFICATION-MIB DEFINITIONS ::= BEGIN
	IMPORTS
		MODULE-IDENTITY, NOTIFICATION-TYPE
			FROM SNMPv2-SMI
		freeradiusObjects
			FROM FREERADIUS-MGMT-MIB
		freeRadius
			FROM FREERADIUS-SMI
		radiusAuthServerAddress,radiusAuthClientServerPortNumber
			FROM RADIUS-AUTH-CLIENT-MIB
		radiusAuthServIdent
			FROM RADIUS-AUTH-SERVER-MIB
		radiusd
			FROM FREERADIUS-PRODUCT-RADIUSD-MIB;

freeRadiusNotificationMib MODULE-IDENTITY
	LAST-UPDATED "201012170000Z"
	ORGANIZATION "FREERADIUS project"
	CONTACT-INFO
		"FreeRADIUS Network Object Model Environment project

		see https://freeradius.org for contact persons of a particular
		area or subproject of FREERADIUS.

		Administrative contact for MIB module:

		Alan DeKok

		email: aland@freeradius.org"
	DESCRIPTION
		"FreeRADIUS Notification MIBs."
	::= { freeRadius 4 }

serverGlobal  OBJECT IDENTIFIER ::= { freeRadiusNotificationMib 1 }

serverStart NOTIFICATION-TYPE
       OBJECTS { radiusObject }
       STATUS current
       DESCRIPTION "Notification that the server has started"
       ::= { serverGlobal 1 }

serverStop NOTIFICATION-TYPE
       OBJECTS { radiusObject }
       STATUS current
       DESCRIPTION "Notification that the server is stopping"
       ::= { serverGlobal 2 }

serverMaxRequests NOTIFICATION-TYPE
       OBJECTS { radiusObject }
       STATUS current
       DESCRIPTION "Notification that the server has hit the max_requests limit"
       ::= { serverGlobal 3 }

serverSignal  OBJECT IDENTIFIER ::= { serverGlobal 4 }

signalHup NOTIFICATION-TYPE
       OBJECTS { radiusObject }
       STATUS current
       DESCRIPTION "Notification that the server has received a HUP signal"
       ::= { serverSignal 1 }

signalTerm NOTIFICATION-TYPE
       OBJECTS { radiusObject }
       STATUS current
       DESCRIPTION "Notification that the server has received a TERM signal"
       ::= { serverSignal 2 }

serverThread  OBJECT IDENTIFIER ::= { serverGlobal 5 }

threadStart NOTIFICATION-TYPE
       OBJECTS { radiusObject }
       STATUS current
       DESCRIPTION "Notification that a thread has started"
       ::= { serverThread 1 }

threadStop NOTIFICATION-TYPE
       OBJECTS { radiusObject }
       STATUS current
       DESCRIPTION "Notification that a thread has stopped"
       ::= { serverThread 2 }

threadUnresponsive NOTIFICATION-TYPE
       OBJECTS { radiusObject }
       STATUS current
       DESCRIPTION "Notification that a child thread is unresponsive"
       ::= { serverThread 3 }

threadMaxThreads NOTIFICATION-TYPE
       OBJECTS { radiusObject }
       STATUS current
       DESCRIPTION "Notification that the max_threads limit has been reached"
       ::= { serverThread 4 }

serverModules  OBJECT IDENTIFIER ::= { freeRadiusNotificationMib 2 }

serverModuleGeneric  OBJECT IDENTIFIER ::= { serverModules 1 }

serverModuleConnectionUp NOTIFICATION-TYPE
       OBJECTS { radiusdModuleName,
		 radiusdModuleInstance,
		 radiusdConnectionPoolServer,
		 radiusdConnectionPoolPort }
       STATUS current
       DESCRIPTION "Notification that the module has opened a new connection"
       ::= { serverModuleGeneric 1 }

serverModuleConnectionDown NOTIFICATION-TYPE
       OBJECTS { radiusdModuleName,
		 radiusdModuleInstance,
		 radiusdConnectionPoolServer,
		 radiusdConnectionPoolPort }
       STATUS current
       DESCRIPTION "Notification that the module has dropped a connection"
       ::= { serverModuleGeneric 2 }

serverModuleConnectionNone NOTIFICATION-TYPE
       OBJECTS { radiusdModuleName,
		 radiusdModuleInstance,
		 radiusdConnectionPoolServer,
		 radiusdConnectionPoolPort }
       STATUS current
       DESCRIPTION "Notification that the module has no connections"
       ::= { serverModuleGeneric 3 }

serverModuleConnectionFail NOTIFICATION-TYPE
       OBJECTS { radiusdModuleName,
		 radiusdModuleInstance,
		 radiusdConnectionPoolServer,
		 radiusdConnectionPoolPort }
       STATUS current
       DESCRIPTION "Notification that the module has failed to open a new connection"
       ::= { serverModuleGeneric 4 }

serverModuleConnectionReservedPeriodMax NOTIFICATION-TYPE
       OBJECTS { radiusdModuleName,
		 radiusdModuleInstance,
		 radiusdConnectionPoolServer,
		 radiusdConnectionPoolPort }
       STATUS current
       DESCRIPTION "Notification that the period a connection was reserved for exceeded the configured maximum"
       ::= { serverModuleGeneric 5 }

serverModuleConnectionReservedPeriodMin NOTIFICATION-TYPE
       OBJECTS { radiusdModuleName,
		 radiusdModuleInstance,
		 radiusdConnectionPoolServer,
		 radiusdConnectionPoolPort }
       STATUS current
       DESCRIPTION "Notification that the period a connection was reserved for was lower than the configured minimum"
       ::= { serverModuleGeneric 6 }

serverModuleConnectionPoolReconnect NOTIFICATION-TYPE
       OBJECTS { radiusdModuleName,
		 radiusdModuleInstance,
		 radiusdConnectionPoolServer,
		 radiusdConnectionPoolPort }
       STATUS current
       DESCRIPTION "Notification that all connections for this pool are being re-established"
       ::= { serverModuleGeneric 7 }

serverModuleHup NOTIFICATION-TYPE
       OBJECTS { radiusdModuleName,
		 radiusdModuleInstance,
		 radiusdConnectionPoolServer,
		 radiusdConnectionPoolPort }
       STATUS current
       DESCRIPTION "Notification that the module has been HUP'd via radmin"
       ::= { serverModuleGeneric 8 }

serverModuleConnectionHalted NOTIFICATION-TYPE
       OBJECTS { radiusdModuleName,
		 radiusdModuleInstance,
		 radiusdConnectionPoolServer,
		 radiusdConnectionPoolPort }
       STATUS current
       DESCRIPTION "Notification a module connection has entered the halted state"
       ::= { serverModuleGeneric 9 }

serverModuleConnectionInit NOTIFICATION-TYPE
       OBJECTS { radiusdModuleName,
		 radiusdModuleInstance,
		 radiusdConnectionPoolServer,
		 radiusdConnectionPoolPort }
       STATUS current
       DESCRIPTION "Notification a module connection has entered the init state"
       ::= { serverModuleGeneric 10 }

serverModuleConnectionConnecting NOTIFICATION-TYPE
       OBJECTS { radiusdModuleName,
		 radiusdModuleInstance,
		 radiusdConnectionPoolServer,
		 radiusdConnectionPoolPort }
       STATUS current
       DESCRIPTION "Notification a module connection has entered the connecting state"
       ::= { serverModuleGeneric 11 }

serverModuleConnectionFull NOTIFICATION-TYPE
       OBJECTS { radiusdModuleName,
		 radiusdModuleInstance,
		 radiusdConnectionPoolServer,
		 radiusdConnectionPoolPort }
       STATUS current
       DESCRIPTION "Notification a module connection has entered the full state"
       ::= { serverModuleGeneric 12 }

serverModuleConnectionInactive NOTIFICATION-TYPE
       OBJECTS { radiusdModuleName,
		 radiusdModuleInstance,
		 radiusdConnectionPoolServer,
		 radiusdConnectionPoolPort }
       STATUS current
       DESCRIPTION "Notification a module connection has entered the inactive state"
       ::= { serverModuleGeneric 13 }

serverModuleConnectionInactiveDraining NOTIFICATION-TYPE
       OBJECTS { radiusdModuleName,
		 radiusdModuleInstance,
		 radiusdConnectionPoolServer,
		 radiusdConnectionPoolPort }
       STATUS current
       DESCRIPTION "Notification a module connection has entered the inactive-draining state"
       ::= { serverModuleGeneric 14 }

serverModuleConnectionDraining NOTIFICATION-TYPE
       OBJECTS { radiusdModuleName,
		 radiusdModuleInstance,
		 radiusdConnectionPoolServer,
		 radiusdConnectionPoolPort }
       STATUS current
       DESCRIPTION "Notification a module connection has entered the draining state"
       ::= { serverModuleGeneric 15 }

serverModuleConnectionDrainingToFree NOTIFICATION-TYPE
       OBJECTS { radiusdModuleName,
		 radiusdModuleInstance,
		 radiusdConnectionPoolServer,
		 radiusdConnectionPoolPort }
       STATUS current
       DESCRIPTION "Notification a module connection has entered the draining-to-free state"
       ::= { serverModuleGeneric 16 }

homeServer  OBJECT IDENTIFIER ::= { freeRadiusNotificationMib 3 }

--
--  For now, we only support IPv4 traps, and we support only UDP.
--  We can add IPv6 and TCP / TLS later.
--
--  We also use the "authserver" fields for both authentication and accounting
--  servers.
--
homeServerAlive NOTIFICATION-TYPE
       OBJECTS { radiusAuthServerAddress,
		 radiusAuthClientServerPortNumber,
		 radiusAuthServIdent }
       STATUS current
       DESCRIPTION "Notification that a home server is alive"
       ::= { homeServer 1 }

homeServerZombie NOTIFICATION-TYPE
       OBJECTS { radiusAuthServerAddress,
		 radiusAuthClientServerPortNumber,
		 radiusAuthServIdent }
       STATUS current
       DESCRIPTION "Notification that a home server is zombie"
       ::= { homeServer 2 }

homeServerDead NOTIFICATION-TYPE
       OBJECTS { radiusAuthServerAddress,
		 radiusAuthClientServerPortNumber,
		 radiusAuthServIdent }
       STATUS current
       DESCRIPTION "Notification that a home server is dead"
       ::= { homeServer 3 }

homeServerPool  OBJECT IDENTIFIER ::= { freeRadiusNotificationMib 4 }

homeServerPoolNormal NOTIFICATION-TYPE
       OBJECTS { radiusdConfigName }
       STATUS current
       DESCRIPTION "Notification that the pool is operating normally"
       ::= { homeServerPool 1 }

homeServerPoolFallback NOTIFICATION-TYPE
       OBJECTS { radiusdConfigName }
       STATUS current
       DESCRIPTION "Notification that the pool is in fallback mode"
       ::= { homeServerPool 2 }

END
